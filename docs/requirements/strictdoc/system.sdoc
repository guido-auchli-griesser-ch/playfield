[DOCUMENT]
TITLE: Test System Requirements
REQ_PREFIX: AUG-SYRS-

[GRAMMAR]
IMPORT_FROM_FILE: system.sgra

[TEXT]
STATEMENT: >>>
SPDX-License-Identifier: Apache-2.0
<<<

[REQUIREMENT]
UID: AUG-SYRS-1
STATUS: Draft
TYPE: Functional
COMPONENT: Hardware Architecture Interface
TITLE: Architecture Layer Interface
STATEMENT: >>>
The RTOS shall provide a framework to communicate with a set of hardware architectural services.
<<<
USER_STORY: >>>
As a RTOS user I want to be able to easily switch my application to a different MCU architecture (x86, ARM Cortex-M/A, RISCV etc.).
<<<

[REQUIREMENT]
UID: AUG-SYRS-2
STATUS: Draft
TYPE: Functional
COMPONENT: Hardware Architecture Interface
TITLE: Support multiprocessor management
STATEMENT: >>>
The RTOS shall support symmetric multiprocessing on multiple cores.
<<<
USER_STORY: >>>
As a RTOS user I want to use OS on multi core (SMP-)MCUs/MPUs.
<<<
RELATIONS:
- TYPE: Parent
  VALUE: AUG-SYRS-1
